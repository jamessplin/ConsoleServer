module sonic-console-server {
    yang-version 1.1;

    namespace "http://github.com/sonic-net/sonic-console-server";
    prefix cs;

    description
        "SONiC console server configuration model.";

    revision 2026-06-12 {
        description
            "Initial revision.";
    }

    container sonic-console-server {
        container CONSOLE_SERVER_PORT {
            list CONSOLE_SERVER_PORT_LIST {
                key "port";
                unique "label";

                leaf port {
                    type uint16 {
                        range "1..256";
                    }
                    description
                        "Serial line number.";
                }

                leaf baudrate {
                    type uint32 {
                        range "300 | 1200 | 2400 | 4800 | 9600 | 19200 | 38400 | 57600 | 115200 | 230400 | 460800 | 921600";
                    }
                    default "115200";
                    description
                        "Supported serial baud rate.";
                }

                leaf databits {
                    type uint8 {
                        range "5..8";
                    }
                    default "8";
                }

                leaf parity {
                    type enumeration {
                        enum none;
                        enum even;
                        enum odd;
                        enum mark;
                        enum space;
                    }
                    default "none";
                }

                leaf stopbits {
                    type uint8 {
                        range "1..2";
                    }
                    default "1";
                }

                leaf flowcontrol {
                    type enumeration {
                        enum none;
                        enum rtscts;
                        enum xonxoff;
                    }
                    default "none";
                }

                leaf mode {
                    type enumeration {
                        enum exclusive;
                        enum shared;
                    }
                    default "shared";
                }

                leaf max_clients {
                    type uint8 {
                        range "1..4";
                    }
                    default "1";
                }

                leaf idle_timeout {
                    type uint32 {
                        range "0..86400";
                    }
                    default "600";
                    description
                        "Idle timeout in seconds. A value of 0 disables the idle timeout. "
                      + "The maximum supported value is 86400 seconds.";
                }

                leaf label {
                    type string {
                        length "1..16";
                    }
                    description
                        "User-friendly serial line label. The platform "
                      + "initialization and shared config manager explicitly "
                      + "materialize COM<port> in ConfigDB when no custom "
                      + "label is configured, and restore COM<port> when a "
                      + "blank label is explicitly provided.";
                }
            }
        }

        container CONSOLE_SERVER_GROUP {
            list CONSOLE_SERVER_GROUP_LIST {
                key "groupname";

                leaf groupname {
                    type string {
                        length "1..32";
                    }
                }

                leaf role {
                    type enumeration {
                        enum operator;
                        enum console_user;
                        enum admin;
                    }
                    default "console_user";
                }
            }
        }

        container CONSOLE_SERVER_GROUP_PORT {
            list CONSOLE_SERVER_GROUP_PORT_LIST {
                key "groupname port";

                leaf groupname {
                    type leafref {
                        path "/cs:sonic-console-server/cs:CONSOLE_SERVER_GROUP/cs:CONSOLE_SERVER_GROUP_LIST/cs:groupname";
                    }
                }

                leaf port {
                    type leafref {
                        path "/cs:sonic-console-server/cs:CONSOLE_SERVER_PORT/cs:CONSOLE_SERVER_PORT_LIST/cs:port";
                    }
                }
            }
        }

        container CONSOLE_SERVER_USER {
            list CONSOLE_SERVER_USER_LIST {
                key "username";

                leaf username {
                    type string {
                        length "1..32";
                        pattern '[A-Za-z_][A-Za-z0-9_-]*';
                    }
                }

                leaf role {
                    type enumeration {
                        enum none;
                        enum operator;
                        enum console_user;
                        enum admin;
                    }
                    default "none";
                }
            }
        }

        container CONSOLE_SERVER_USER_GROUP {
            list CONSOLE_SERVER_USER_GROUP_LIST {
                key "username groupname";

                leaf username {
                    type leafref {
                        path "/cs:sonic-console-server/cs:CONSOLE_SERVER_USER/cs:CONSOLE_SERVER_USER_LIST/cs:username";
                    }
                }

                leaf groupname {
                    type leafref {
                        path "/cs:sonic-console-server/cs:CONSOLE_SERVER_GROUP/cs:CONSOLE_SERVER_GROUP_LIST/cs:groupname";
                    }
                }
            }
        }
    }

    rpc console-server-user-add {
        description
            "Create, update, or import a console-server user.";

        input {
            leaf username {
                type string {
                    length "1..32";
                    pattern '[A-Za-z_][A-Za-z0-9_-]*';
                }
                mandatory true;
            }

            leaf password {
                type string {
                    length "1..128";
                }
                description
                    "Required when creating a new Linux user. Optional when updating or importing an existing Linux user.";
            }

            leaf role {
                type enumeration {
                    enum none;
                    enum operator;
                    enum console_user;
                    enum admin;
                }
                default "none";
            }

            leaf-list groups {
                type leafref {
                    path "/cs:sonic-console-server/cs:CONSOLE_SERVER_GROUP/cs:CONSOLE_SERVER_GROUP_LIST/cs:groupname";
                }
            }
        }
    }

    rpc console-server-user-password-set {
        description
            "Update the password of an existing Linux user.";

        input {
            leaf username {
                type string {
                    length "1..32";
                    pattern '[A-Za-z_][A-Za-z0-9_-]*';
                }
                mandatory true;
            }

            leaf password {
                type string {
                    length "1..128";
                }
                mandatory true;
            }
        }
    }

}
